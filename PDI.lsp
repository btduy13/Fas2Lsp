;;;;;;;;;;;;;;;;;;;;;;;;;;;;;;;;;;;;;;;;;;;;;;;;;;;;;;;;;;;;;;;;
;; Decompiled from FAS4 format (reverse engineered)
;; File: PDI.fas
;;;;;;;;;;;;;;;;;;;;;;;;;;;;;;;;;;;;;;;;;;;;;;;;;;;;;;;;;;;;;;;;

(defun c:PDI (/ dict_name items_purged dict_obj continue)
  ;; Bytecode Analysis Results:
  ;; - Analyzed 513 bytes of bytecode
  ;; - Extracted 94 strings
  ;; Extracted strings (by offset):
  ;;   [0000] "fsrrr{Vr#sQrsrx%Urrrfsssr{Pr.rrjqrstSrstRrstmrstlrGrorqksrd{WrtnrGrirqGshrqGskrqtSrqSr"
  ;;   [0007] "$u%"
  ;;   [0009] "TvUTU_"
  ;;   [0011] "$%$.s"
  ;;   [0017] "$$$0%%%$-"
  ;;   [0027] "$x$$<'$%""
  ;;   [0029] "UUMVUTStUTSuUTSJUTSKU`UHUVLTUC\pUSIU`UNUV`TOUV`TLUVStUVtU2"
  ;;   [0037] "89>"
  ;;   [0041] "89>'89>&8"
  ;;   [0045] "`af~`U`}`cya`viE`f|`U`{`cUaz`cUay`cfA`cA`"
  ;;   [0051] "$9$'=%$2-"
  ;;   [0056] "gfpoCf`zfSf}feSg|feSg"
  ;;   [0061] "$"8$"
  ;;   [0066] "8#8;"
  ;;   [0071] "9"8;"
  ;;   [0076] "9!8;>"
  ;;   [0078] "fe`GfeGf"
  ;;   [0085] "$Cx$$$'"
  ;;   [0087] ".rrrqSrGsjrqGsjrq@qGperq"
  ;;   [0095] "9 8;"
  ;;
  ;; NOTE: FAS4 format is proprietary and strings are encoded/compressed
  ;; Full decompilation requires understanding the encoding algorithm
  (princ "FAS4 bytecode analysis: strings extracted but format requires further reverse engineering")
)
